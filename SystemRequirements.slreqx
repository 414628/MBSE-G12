# SystemRequirements

## SystemRequirements!Sheet1: References to SystemRequirements.xlsx (Sheet1) (Container)
Imported from Microsoft Excel

### Sheet1!SN-01: Coverage (Informational)
The minidrone must be able to also cover big crop fields.

### Sheet1!SN-02: Scaring birds (Informational)
The minidrone must scare birds away from crop fields.

### Sheet1!FR-01: Take off and land (Functional)
The quadcopter shall have a maximum angular velocity of at least 180 deg/s.

### Sheet1!FR-02: Perform controlled flight (Functional)
The minidrone should be able to fly according to a six degrees of freedom (6 DOF) movement.

### Sheet1!FR-03: Flight range (Functional)
The range of the minidrone must be at least 10 kilometers, so that it can also cover larger crop fields.

### Sheet1!FR-04: Flight region (Functional)
For testing purposes, the drone should be able to achieve and maintain a constant altitude of 1,5 meters.

### Sheet1!FR-05: Flight control (Functional)
The flight of the drone should be managed from a control system and should operate autonomously so it can fly a predetermined route over a crop field.

### Sheet1!FR-06: Scaring mechanism (Functional)
The drone should be able to make a high pitch sound to scare birds away.

### Sheet1!HR-01: Body (Functional)
The main body protects the other components and also provides structural support. A microphone may be attached to it in order to produce a high pitch sound to scare birds away.

### Sheet1!HR-02: Power module (Functional)
The power module will need to provide enough power to support the propulsion system, flight control and communication modules.

### Sheet1!HR-03: Propulsion module (Functional)
The propulsion module consists of one or more rotor assemblies that contain a propeller and a motor driving the propeller.

### Sheet1!HR-04: Flight control module (Functional)
The flight control module consists of a control system module and a path planning module.

### Sheet1!HR-05: Control system (Functional)
The control system module controls the behavior of the minidrone while in flight.

### Sheet1!HR-06: Path planning (Functional)
The system should be able to plan its own path and update it based on user requests or outside factors.

### Sheet1!HR-07: Noise module (Functional)
The minidrone should have a speaker or other sensor to make it possible to produce a high pitch sound to scare birds away.

### Sheet1!HR-08: Sensor module (Functional)
The minidrone should have a redundant IMU for improved calibration and pose estimation and encoder sensors to measure velocity of propeller motors to use as an input to the flight control modules.

### Sheet1!HR-09: Communication module (Functional)
The minidrone must have Wi-Fi network communication and/or radio/Bluetooth communication.
